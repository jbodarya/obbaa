module bbf-network-function-types {
  yang-version 1.1;
  namespace "urn:bbf:yang:bbf-network-function-types";
  prefix bbf-nf-types;

  import bbf-device-types {
    prefix bbf-dvct;
  }

  organization
    "Broadband Forum <https://www.broadband-forum.org>
     CloudCO Project Stream";

  contact
    "Comments or questions about this Broadband Forum YANG module
     should be directed to <mailto:help@broadband-forum.org>.

     Editor:      Tim Carey, Nokia

     Editor:      Dechao Zhang, China Mobile

     PS Leader:   Yves Hertoghs, VMWare

     WA Director: George Dobrowski, Morris Creek Consulting

     WA Director: Bruno Cornaglia, Vodafone";

  description
    "This module contains a collection of YANG definitions for 
     types associated with BBF Network Functions.

     Copyright (c) 2019-2021, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of WT-454; see
     the WT itself for full legal notices.";

   revision 2021-03-01 {
    description
      "Initial release";
    reference
      "Broadband Forum TR-451";
  }

  // Identities
  // Network function types
  identity nf-type {
    description
      "Base identity for defining network function (NF) types.";
  } 
  identity pnf-type {
    base bbf-dvct:device-type;
    base nf-type; 
    description
      "Base identity from which Physical network function (PNF) types
       are derived.";
  }
  identity vnf-type {
    base nf-type;
    description
      "Base identity from which specific virtual network functions 
       types are derived.";
  } 
  identity access-vnf-type {
    base vnf-type;
    description
      "Base identity from which specific access virtual network 
       functions types are derived.";
  }
  identity vomci-function-type {
    base access-vnf-type;
    description
      "Virtual OMCI network function.";
  }
  identity vomci-proxy-type {
    base access-vnf-type;
    description
      "Virtual OMCI Proxy network function.";
  }
  identity voltmf-type {
    base access-vnf-type;
    description
      "Virtual OLT management network function.";
  }

  identity dolt-dhcpra-type {
     base access-vnf-type;
     description
      "DHCP RA network function for D-OLT";
  }

  identity dolt-pppoeiatype {
     base access-vnf-type;
     description
      "PPPoE IA network function for D-OLT";
  }

  identity dolt-igmp-type {
     base access-vnf-type;
     description
      "IGMP networkfunction for D-OLT";
  }

  identity dolt-onuauthtype {
     base access-vnf-type;
     description
      "ONU authenticationnetwork function for DOLT";
  }

  identity dolt-dba-type {
     base access-vnf-type;
     description
      "Virtual DBA network function for D-D-OLT";
  }
}
