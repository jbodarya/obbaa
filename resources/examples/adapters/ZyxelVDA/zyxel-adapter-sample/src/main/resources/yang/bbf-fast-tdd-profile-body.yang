submodule bbf-fast-tdd-profile-body {
  yang-version 1.1;
  belongs-to bbf-fast {
    prefix bbf-fast;
  }

  include bbf-fast-base;

  organization
    "Broadband Forum <https://www.broadband-forum.org>
     Common YANG Work Area";

  contact
    "Comments or questions about this Broadband Forum YANG module
     should be directed to <mailto:help@broadband-forum.org>.

     Editor:      Ken Kerpez, ASSIA, Inc.

     Editor:      Joey Boyd, ADTRAN

     PS Leader:   Ken Kerpez, ASSIA, Inc.

     PS Leader:   Joey Boyd, ADTRAN

     WA Director: Sven Ooghe, Nokia

     WA Director: Joey Boyd, ADTRAN";

  description
    "This submodule contains a collection of YANG definitions for
     managing TDD profiles.

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a1; see
     the TR itself for full legal notices.";

  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum_1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping time-division-duplexing-parameters {
    description
      "Time division duplexing (TDD) configuration parameters.";
    reference
      "ITU-T G.997.2 clause 7.1.1.";

    leaf total-symbol-periods {
      type uint8 {
        range "23 | 36";
      }
      default "36";
      description
        "Defines the total number of symbol periods in a TDD
         frame.";
      reference
        "ITU-T G.997.2 clause 7.1.1.1 (MF); ITU-T G.9701 clause
         10.5.";
    }

    leaf downstream-symbol-periods {
      type uint8 {
        range "6..32";
      }
      must
        "(../total-symbol-periods = 23 and .>= 6 and .<= 19) or
         (../total-symbol-periods = 36 and .>= 10 and .<= 32)" {
        description
          "If the total symbol periods is 23, the number of downstream
           symbol periods must be between 6 to 19 inclusive. If the 
           total symbol periods is 36, the number of downstream symbol
           periods must be between 10 to 32 inclusive";
      }
      default "28";
      description
        "Defines the total number of symbol positions in a TDD frame
         allocated for downstream transmission. The total number of
         symbol positions in a TDD frame allocated for upstream
         transmission is calculated as Mus = MF-1-Mds.";

      reference
        "ITU-T G.997.2 clause 7.1.1.2 (Mds); ITU-T G.9701 Clause
         10.5";
    }

    leaf cyclic-extension {
      type uint8 {
        range "4 | 8 | 10 | 12 | 14 | 16 | 20 | 24 | 30 | 33";
      }
      units "N/64 samples";
      default "10";
      description
        "Defines the cyclic extension(Lcp) to be used. The units
         are in N/64 samples, where N = index of the highest
         supported downstream data-bearing sub-carrier as defined
         for the enabled profile (see Table 6-1/G.9701) plus one.";
      reference
        "ITU-T G.997.2 clause 7.1.1.3; ITU-T G.9701 clause 10.4.4";
    }

    container dynamic-time-assignment {
      if-feature "dta";
      description
        "Configuration of Dynamic Time Assignement (DTA).";

      leaf dta-allowed {
        type enumeration {
          enum "none" {
            description
              "Dynamic Time Assignment is not allowed.";
          }
          enum "idta" {
            if-feature "annex-x";
            description
              "Operation according to ITU-T G.9701 Annex X (iDTA) is 
               allowed. If 'annex-x-mode' in the vectoring profile
               is configured as 'forbidden', then this value must not
               be configured.";
          }
          enum "cdta" {
            if-feature "annex-d";
            description
              "Operation according to ITU-T G.9701 Annex D (cDTA) is 
               allowed. If 'annex-d-mode' in the vectoring profile
               is configured as 'forbidden', then this value must not
               be configured.";
          }
        }
        default "none";
        description
          "The type of Dynamic Time Assignment allowed.";
        reference
          "ITU-T G.9701 clause X.6.7.2 and T.2.2;
           ITU-T G.9701 clause D.5.7.2 and T.2.2.1";
      }

      leaf preferred-mds {
        type uint8 {
          range "5..31";
        }
        must
          "((../dta-allowed='idta' and ../../total-symbol-periods =
           23 and .>= 5 and .<= 17) or (../dta-allowed='idta' and 
           ../../total-symbol-periods = 36 and .>= 5 and .<= 30) or
           (../dta-allowed='cdta' and ../../total-symbol-periods = 
           23 and .>= 6 and .<= 19) or (../dta-allowed='cdta' and 
           ../../total-symbol-periods = 36 and .>= 10 and .<= 31) 
           or ../dta-allowed='none') and (. >= ../minimum-mds) and 
           (. <= ../maximum-mds)" {
          description
            "Restricts the valid range for the preferred Mds depending
             on MF and DTA type allowed.

             The preferred Mds for DTA must be equal to or higher than
             the minimum Mds for DTA and less than or equal to the 
             maximum Mds for DTA.";
        }
        default "28";
        description
          "Provides the number of downstream symbol
           positions in a TDD frame requested by the DRA
           at the first opportunity upon entering showtime
           of a line on which DTA operation is enabled.
           If MF=23, a value different from the default
           value needs to be configured.";
        reference
          "ITU-T clause T.2.3";
      }

      leaf maximum-step-size {
        type uint8 {
          range "1..25";
        }
        must
          "(../dta-allowed='idta' and ../../total-symbol-periods = 
           23 and .>= 1 and .<= 12) or (../dta-allowed='idta' and 
           ../../total-symbol-periods = 36 and .>= 1 and .<= 25) or
           (../dta-allowed='cdta' and ../../total-symbol-periods = 
           23 and .>= 1 and .<= 13) or (../dta-allowed='cdta' and 
           ../../total-symbol-periods = 36 and .>= 1 and .<= 21) or
           ../dta-allowed='none'" {
          description
            "Restricts the valid range for the maximum step size 
             depending on MF and DTA type allowed.";
        }
        default "25";
        description
          "Defines the maximum step size for Mds requested by the DRA 
           for a single DTA update. For configurations other than 
           iDTA allowed with MF=36, a value different from the 
           default value needs to be configured.";
        reference
          "ITU-T G.9701 clause T.2.3";
      }

      leaf minimum-time-between-updates {
        type uint16 {
          range "0..16383";
        }
        units "0.01 second";
        default "0";
        description
          "Provides the minimum time between any two successive 
           DTA updates during showtime.";
        reference
          "ITU-T G.997.2 clause T.2.2.8 (DTA_MIN_TIME); 
           ITU-T G.9701 clause T.2.10";
      }

      leaf minimum-mds {
        type uint8 {
          range "5..31";
        }
        must
          "((../dta-allowed='idta' and ../../total-symbol-periods =
           23 and .>= 5 and .<= 17) or (../dta-allowed='idta' and 
           ../../total-symbol-periods = 36 and .>= 5 and .<= 30) or
           (../dta-allowed='cdta' and ../../total-symbol-periods = 
           23 and .>= 6 and .<= 19) or (../dta-allowed='cdta' and 
           ../../total-symbol-periods = 36 and .>= 10 and .<= 31) 
           or ../dta-allowed='none') and . <= 
           ../../downstream-symbol-periods" {
          description
            "Restricts the valid range for the minimum Mds 
             depending on MF, DTA type allowed, and downstream symbol
             periods.";
        }
        default "5";
        description
          "Provides the minimum number of downstream symbol
           positions Mds in a TDD frame that shall be 
           requested by the DRA. For configurations with 
           cDTA allowed, a value different from the 
           default value needs to be configured.";
        reference
          "ITU-T G.9701 clause T.2.5";
      }

      leaf maximum-mds {
        type uint8 {
          range "5..31";
        }
        must
          "((../dta-allowed='idta' and ../../total-symbol-periods =
           23 and .>= 5 and .<= 17) or (../dta-allowed='idta' and 
           ../../total-symbol-periods = 36 and .>= 5 and .<= 30) or
           (../dta-allowed='cdta' and ../../total-symbol-periods = 
           23 and .>= 6 and .<= 19) or (../dta-allowed='cdta' and 
           ../../total-symbol-periods = 36 and .>= 10 and .<= 31) 
           or ../dta-allowed='none') and . <= 
           ../../downstream-symbol-periods" {
          description
            "Restricts the valid range for the maximum Mds 
             depending on MF, DTA type allowed, and downstream symbol
             periods.";
        }
        default "30";
        description
          "Provides the maximum number of downstream symbol
           positions Mds in a TDD frame that shall be 
           requested by the DRA. For configurations with MF=23, 
           a value different from the default value needs to be 
           configured.";
        reference
          "ITU-T G.9701 clause X.6.7.4 and T.2.6.";
      }

      leaf cdta-procedure-control {
        when "../dta-allowed='cdta'" {
          description
            "Only applicable when cDTA is configured.";
        }
        if-feature "annex-d";
        type enumeration {
          enum "one-or-two-step" {
            value 0;
            description
              "DRA is allowed to use the one-step or two-step 
               cDTA procedure (see clause Y.5.6)";
          }
          enum "one-step-only" {
            value 1;
            description
              "DRA shall use the one-step cDTA procedure only 
               (see clause Y.5.6).";
          }
          enum "two-step-only" {
            value 2;
            description
              "DRA shall use the two-step procedure only 
               (see clause Y.5.6). This value is intended 
               to be used for test purposes.";
          }
        }
        default "one-or-two-step";
        description
          "Provides the procedure type that the DRA is allowed to 
           apply. If the CDTA_PROC_CTRL is set to 2 and the FTU-O does
           not support the two-step procedure, no cDTA procedure is 
           triggered by the DRA.";
        reference
          "ITU-T G.997.2 clause T.2.7 (CDTA_PROC_CTRL); 
           ITU-T G.9701 clause T.2.9.";
      }
    }
  }

  grouping tdd-profile {
    description
      "Defines the contents of a Time Division Duplexing Profile.";

    uses time-division-duplexing-parameters;
  }
}
