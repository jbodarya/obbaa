submodule bbf-l2-forwarding-flooding-policies {
  yang-version 1.1;
  belongs-to bbf-l2-forwarding {
    prefix bbf-l2-fwd;
  }

  import bbf-yang-types {
    prefix bbf-yang;
  }

  import bbf-interface-usage {
    prefix bbf-if-usg;
  }

  import bbf-frame-classification {
    prefix bbf-classif;
  }

  include bbf-l2-forwarding-base;
  include bbf-l2-forwarding-forwarders;

  organization
    "Broadband Forum <https://www.broadband-forum.org>
     Common YANG Work Area";

  contact
    "Comments or questions about this Broadband Forum YANG module
     should be directed to <mailto:help@broadband-forum.org>.

     Editor:      Joey Boyd, ADTRAN

     Editor:      Ludwig Pauwels, Nokia

     PS Leader:   Joey Boyd, ADTRAN

     PS Leader:   Ken Kerpez, ASSIA

     WA Director: Joey Boyd, ADTRAN

     WA Director: Sven Ooghe, Nokia";

  description
    "This submodule contains a collection of YANG definitions for
     managing flooding policies.

     Copyright (c) 2017-2018, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383; see
     the TR itself for full legal notices.";

  revision 2018-12-03 {
    description
      "Amendment 2.
       * Approval Date:    2018-12-03.
       * Publication Date: 2018-12-03.";
    reference
      "TR-383a2: Common YANG Modules
               <https://www.broadband-forum.org/technical/download/
                        TR-383_Amendment-2.pdf>";
  }
  revision 2018-07-13 {
    description
      "Initial revision.
       * Approval Date:    2018-06-04.
       * Publication Date: see revision date above.";
    reference
      "TR-383: Common YANG Modules
               <https://www.broadband-forum.org/technical/download/
                        TR-383_Amendment-1.pdf>";
  }
  revision 2017-05-08 {
    description
      "Initial revision.
       * Approval Date:    see revision date above.
       * Publication Date: 2017-06-02.";
    reference
      "TR-383: Common YANG Modules
               <https://www.broadband-forum.org/technical/download/
                        TR-383.pdf>";
  }

  feature flooding-policies {
    description
      "Indicates support for flooding policies.";
  }

  feature flooding-policies-profiles {
    description
      "Indicates support for flooding policies profiles.";
  }

  augment '/bbf-l2-fwd:forwarding' {
    description
      "Augment the configuration nodes associated with layer 2
       forwarding with flooding policies profile objects.";

    container flooding-policies-profiles {
      if-feature "flooding-policies-profiles";
      description
        "Contains a set of flooding-policies-profiles.

         The flooding policies define how the system shall forward
         frames in case the other forwarding mechanisms did not come
         to a forwarding decision, e.g. when the destination unicast
         MAC address is not available in the forwarding database.

         For multicast frames this applies when there is no
         corresponding entry found in the (IGMP controled) multicast
         tree.

         For broadcast frames this applies when there is no other
         protocol specific behaviour knowledge.";

      list flooding-policies-profile {
        key "name";

        description
          "The configuration of a flooding policies profile.
           One flooding policies profile can contain multiple
           policies.";

        leaf name {
          type bbf-yang:string-ascii64;
          description
            "The name of a flooding policies profile.";
        }

        list flooding-policy {
          key "name";
          ordered-by user;

          description
            "A flooding-policy defines for the tuple (list of
             in-interface-usages, a frame classification), if and to
             which other interface usages the frame shall be flooded.

             The absence of data for a particular combination results
             in the default forwarding behavior to flood the frame to
             all ports of the forwarder, except the one on which the
             frame is received.";

          leaf name {
            type bbf-yang:string-ascii64;
            description
              "The name of a flooding policy.";
          }

          container in-interface-usages {
            description
              "Identifies the forwarder ports on which the
               classification shall apply. The actual identification
               is indirect: a forwarder port references a VLAN
               sub-interface and this VLAN sub-interface has an
               interface usage.";

            leaf-list interface-usages {
              type bbf-if-usg:interface-usage;
              description
                "List of interface-usages to which the frame
                 classification applies.

                 An empty list means that the classification is
                 applied to none of the interface usages and hence
                 does not make sense.";
            }
          }

          container destination-address {
            description
              "The frame classification to be performed on the
               destination MAC or IP address. Note that the MAC filter
               also allows specification of unicast addresses. If used
               this will apply to frames for which there was no
               forwarding decision identified via other means.";

            uses bbf-classif:frame-destination-match;
          }

          choice frame-forwarding {
            default "discard";
            description
              "Identifies the action to be performed on frames that
               match the classification.";

            case discard {
              leaf discard {
                type empty;
                description
                  "The frame will be discarded.";
              }
            }

            case forward {
              container out-interface-usages {
                description
                  "Identifies the forwarder ports to which the frame
                   shall be forwarded. The actual identification is
                   indirect: a forwarder port references a
                   VLAN sub-interface and this VLAN sub-interface has
                   an interface usage.";

                leaf-list interface-usages {
                  type bbf-if-usg:interface-usage;
                  description
                    "List of interface usages to which the frame shall
                     be forwarded.";
                }
              }
            }
          }
        }
      }
    }
  }

  augment '/bbf-l2-fwd:forwarding/bbf-l2-fwd:forwarders/bbf-l2-fwd:'
        + 'forwarder' {
    description
      "Augment the forwarder configuration with configuration for
       flooding policies.";

    container flooding-policies {
      if-feature "flooding-policies";
      description
        "The flooding-policies define how the system shall forward
         frames in case the other forwarding mechanisms did not come
         to a forwarding decision.

         E.g. when the destination  unicast MAC address is not
         available in the forwarding database. For multicast frames
         this applies when there is no corresponding entry found in
         the (IGMP controled) multicast tree. For broadcast frames
         this applies when there is no other protocol specific
         behaviour knowledge.

         The default behavior for when there is no flooding policy is
         that the frame is flooded to all ports of the forwarder,
         except to the port on which the frame is received. In other
         words, a flooding-policy intends to restrict this flooding.";

      choice flooding-policy-type {
        description
          "Provides alternative ways to define flooding policies.";

        case profile-based {
          if-feature "flooding-policies-profiles";
          leaf flooding-policies-profile {
            type leafref {
              path '/bbf-l2-fwd:forwarding/bbf-l2-fwd:flooding-'
                 + 'policies-profiles/bbf-l2-fwd:flooding-policies-'
                 + 'profile/bbf-l2-fwd:name';
            }
            description
              "A reference to a flooding policies profile.";
          }
        }

        case forwarder-specific {
          list flooding-policy {
            key "name";
            ordered-by user;
            description
              "A flooding-policy defines for the tuple (list of
               in-ports, a frame classification), if and to which
               other ports the frame shall be flooded.

               The absence of data for a particular combination
               results in the default forwarding behavior to flood the
               frame to all ports of the forwarder, except the one on
               which the frame is received.";

            leaf name {
              type bbf-yang:string-ascii64;
              description
                "The name of the flooding policy.";
            }

            container in-ports {
              description
                "List of forwarder ports on which the frame
                 classification applies.";

              choice list-type {
                description
                  "Provides alternatives to provide a single or a set
                   of forwarder ports.

                   The absence of a leaf of this choice means that the
                   classification is applied to none of the ports and
                   hence does not make sense.";

                case forwarder-port {
                  leaf forwarder-port {
                    type leafref {
                      path '../../../../bbf-l2-fwd:ports/bbf-l2-'
                         + 'fwd:port/bbf-l2-fwd:name';
                    }

                    description
                      "A reference to a forwarder port within this
                       forwarder.";
                  }
                }

                case forwarder-port-group {
                  if-feature "forwarder-port-groups";

                  leaf forwarder-port-group {
                    type leafref {
                      path '../../../../bbf-l2-fwd:port-groups/bbf-'
                         + 'l2-fwd:port-group/bbf-l2-fwd:name';
                    }
                    description
                      "A reference to a forwarder port group within
                       this forwarder.";
                  }
                }
              }
            }

            container destination-address {
              description
                "The frame classification to be performed on the
                 destination MAC or IP address. Note that the MAC
                 filter also allows specifation of unicast addresses.
                 If used this will apply to frames for which there was
                 no forwarding decision identified via other means.";

              uses bbf-classif:frame-destination-match;
            }

            choice frame-forwarding {
              default "discard";

              description
                "Specifies how to act on matching frames.";

              case discard {
                leaf discard {
                  type empty;
                  description
                    "The frame shall be discarded.";
                }
              }

              case forward {
                container out-ports {
                  description
                    "List of ports to which the frame shall be
                     forwarded.";

                  choice list-type {
                    description
                      "Specifies how to where to forward the frames.";

                    case forwarder-port {
                      leaf forwarder-port {
                        type leafref {
                          path '../../../../bbf-l2-fwd:ports/bbf-'
                             + 'l2-fwd:port/bbf-l2-fwd:name';
                        }
                        description
                          "A reference to a forwarder port within the
                           same forwarder.";
                      }
                    }

                    case forwarder-port-group {
                      if-feature "forwarder-port-groups";

                      leaf forwarder-port-group {
                        type leafref {
                          path '../../../../bbf-l2-fwd:port-groups/'
                             + 'bbf-l2-fwd:port-group/bbf-l2-fwd:'
                             + 'name';
                        }
                        description
                          "A reference to a forwarder port group
                           within the same forwarder.";
                      }
                    }
                  }
                }
              }
            }
          }
        }
      }
    }
  }
}
