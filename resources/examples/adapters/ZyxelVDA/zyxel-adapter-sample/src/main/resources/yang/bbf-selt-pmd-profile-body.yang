submodule bbf-selt-pmd-profile-body {
  yang-version 1.1;
  belongs-to bbf-selt {
    prefix bbf-selt;
  }

  organization
    "Broadband Forum <https://www.broadband-forum.org>
     Common YANG Work Area";

  contact
    "Comments or questions about this Broadband Forum YANG module
     should be directed to <mailto:help@broadband-forum.org>.

     Editor:      Ken Kerpez, ASSIA, Inc.

     Editor:      Joey Boyd, ADTRAN

     PS Leader:   Ken Kerpez, ASSIA, Inc.

     PS Leader:   Joey Boyd, ADTRAN

     WA Director: Sven Ooghe, Nokia

     WA Director: Joey Boyd, ADTRAN";

  description
    "This submodule contains a collection of YANG definitions for
     managing PMD profiles.

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a1; see
     the TR itself for full legal notices.";

  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum_2.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  typedef uer-measurement-duration {
    type uint8 {
      range "5..240";
    }
    units "1 second";
    description
      "This parameter is the maximum allowed time for SELT 
       uncalibrated echo response measurement, between the time of 
       the start command written by the SELT-PMD-ME, and the time the
       result is available for read operation by SELT-PMD-ME.

       NOTE - The above duration includes internal pre- and 
              post-processing.

       It is configurable between 5 seconds and 240 seconds, in steps
       of 1 second";
    reference
      "ITU-T G.996.2 clause A.2.1.1 (SELT-UER-MMD-C, 
       SELT-UER-MMD-R)";
  }

  typedef qln-measurement-duration {
    type uint8 {
      range "1..240";
    }
    units "1 second";
    description
      "This parameter is the maximum allowed time for SELT quiet line
       noise measurement, between the time of the start command 
       written by the SELT-PMD-ME, and the time the result is 
       available for read operation by SELT-PMD-ME.

       NOTE - The above duration includes internal pre- and 
              post-processing.

       It is configurable between 1 second and 240 seconds, in steps 
       of 1 second.";
    reference
      "ITU-T G.996.2 clause A.2.1.2 (SELT-QLN-MMD-C, 
       SELT-QLN-MMD-R)";
  }

  grouping co-cpe-parameters {
    description
      "Parameters to define the configuration common between the 
       CO SELT PMD and CPE SELT PMD";

    leaf uer-measurement-duration {
      type uer-measurement-duration;
      description
        "The Uncalibrated Echo Response(UER) duration for the  
         SELT PMD";
      reference
        "ITU-T G.996.2 clause A.2.1.1 (SELT-UER-MMD-C, 
         SELT-UER-MMD-R)";
    }

    leaf qln-measurement-duration {
      type qln-measurement-duration;
      description
        "The Quiet Line Noise(QLN) duration for the SELT PMD";
      reference
        "ITU-T G.996.2 clause A.2.1.2 (SELT-QLN-MMD-C, 
         SELT-QLN-MMD-R)";
    }
  }

  grouping pmd-profile {
    description
      "Defines the parameters contained in a PMD profile.";

    container c {
      description
        "Managed objects applicable to the CO SELT PMD";

      uses co-cpe-parameters;
    }

    container r {
      description
        "Managed objects applicable to the CPE SELT PMD";

      uses co-cpe-parameters;
    }
  }
}
