submodule bbf-fast-threshold-management {
  yang-version 1.1;
  belongs-to bbf-fast {
    prefix bbf-fast;
  }

  import bbf-yang-types {
    prefix bbf-yang;
  }

  import bbf-fastdsl {
    prefix bbf-fastdsl;
  }

  import ietf-interfaces {
    prefix if;
  }

  include bbf-fast-base;
  include bbf-fast-perf-types;

  /* Profile bodies */
  include bbf-fast-line-threshold-profile-body;
  include bbf-fast-channel-threshold-profile-body;
  include bbf-fast-threshold-crossing-alert-body;

  organization
    "Broadband Forum <https://www.broadband-forum.org>
     Common YANG Work Area";

  contact
    "Comments or questions about this Broadband Forum YANG module
     should be directed to <mailto:help@broadband-forum.org>.

     Editor:      Ken Kerpez, ASSIA, Inc.

     Editor:      Joey Boyd, ADTRAN

     PS Leader:   Ken Kerpez, ASSIA, Inc.

     PS Leader:   Joey Boyd, ADTRAN

     WA Director: Sven Ooghe, Nokia

     WA Director: Joey Boyd, ADTRAN";

  description
    "This submodule contains a collection of YANG definitions for
     managing performance thresholds for FAST interfaces.

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a1; see
     the TR itself for full legal notices.";

  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  typedef line-threshold-profile-ref {
    type leafref {
      path '/bbf-fast:fast/bbf-fast:thresholds/bbf-fast:line-'
         + 'threshold-profile/bbf-fast:name';
    }
    description
      "Used to reference a line threshold profile";
  }

  typedef channel-threshold-profile-ref {
    type leafref {
      path '/bbf-fast:fast/bbf-fast:thresholds/bbf-fast:channel-'
         + 'threshold-profile/bbf-fast:name';
    }
    description
      "Used to reference a channel threshold profile";
  }

  augment '/bbf-fast:fast/bbf-fast:thresholds' {
    description
      "Data nodes to support performance threshold profiles and
       templates.";

    list line-threshold-profile {
      key "name";
      description
        "Profile defining thresholds for line specific
         performance parameters.";

      leaf name {
        type bbf-yang:string-ascii64;
        description
          "Uniquely identifies the line threshold profile.";
      }

      uses line-thresholds;
    }

    list channel-threshold-profile {
      key "name";
      description
        "Profile defining thresholds for bearer channel specific 
         performance parameters.";

      leaf name {
        type bbf-yang:string-ascii64;
        description
          "Uniquely identifies the channel threshold profile.";
      }

      uses channel-thresholds;
    }
  }

  augment '/if:interfaces-state/if:interface/bbf-fastdsl:line/bbf-'
        + 'fast:line' {
    description
      "Augment the line to add threshold state data.";

    notification fast-15min-threshold-crossing-alert {
      description
        "A threshold has been crossed during the current 15 minute
         interval.";

      leaf tca-identity {
        type identityref {
          base fast-15min-threshold-crossing-alert;
        }
        mandatory true;
        description
          "A unique identity associated with each threshold.";
      }
    }

    notification fast-24hr-threshold-crossing-alert {
      if-feature "performance-24hr";
      description
        "A threshold has been crossed during the current 24 hour
         interval.";

      leaf tca-identity {
        type identityref {
          base fast-24hr-threshold-crossing-alert;
        }
        mandatory true;
        description
          "A unique identity associated with each threshold.";
      }
    }
  }
}
