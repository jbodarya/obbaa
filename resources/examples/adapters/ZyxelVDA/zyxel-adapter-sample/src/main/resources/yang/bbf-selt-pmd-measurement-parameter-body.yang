submodule bbf-selt-pmd-measurement-parameter-body {
  yang-version 1.1;
  belongs-to bbf-selt {
    prefix bbf-selt;
  }

  organization
    "Broadband Forum <https://www.broadband-forum.org>
     Common YANG Work Area";

  contact
    "Comments or questions about this Broadband Forum YANG module
     should be directed to <mailto:help@broadband-forum.org>.

     Editor:      Ken Kerpez, ASSIA, Inc.

     Editor:      Joey Boyd, ADTRAN

     PS Leader:   Ken Kerpez, ASSIA, Inc.

     PS Leader:   Joey Boyd, ADTRAN

     WA Director: Sven Ooghe, Nokia

     WA Director: Joey Boyd, ADTRAN";

  description
    "This submodule contains a collection of YANG definitions for
     SELT-PMD measurement parameters.

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a1; see
     the TR itself for full legal notices.";

  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2017-11-27 {
    description
      "Corrigendum 2 (fixes to the previous revision).
       * Approval Date:    see revision date above.
       * Publication Date: 2018-01-19.";
    reference
      "TR-355c2: YANG Modules for FTTdp Management
                 <https://www.broadband-forum.org/technical/download/
                        TR-355_Corrigendum_2.pdf>";
  }
  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum_1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  feature extended-bandwidth-selt-uer {
    description
      "Indicates support for extended bandwidth SELT for reporting
       Uncalibrated Echo Response (UER).";
  }

  feature extended-bandwidth-selt-qln {
    description
      "Indicates support for extended bandwidth SELT for reporting
       Quiet Line Noise (QLN).";
  }

  typedef sub-carrier-index {
    type uint16 {
      range "0..8191";
    }
    description
      "Identifies a sub-carrier.";
  }

  typedef per-sub-carrier-uint8 {
    type binary {
      length "0..8192";
    }
    description
      "A binary type where each octet represents data belonging to 
       a sub-carrier group. The first octet represents sub-carrier 
       group 0 and the last octet represents the sub-carrier 
       group (length - 1).";
  }

  typedef per-sub-carrier-int32-tuple {
    type binary {
      length "0..65536";
    }
    description
      "A binary type where each group of 8 octets represents a tuple. 
       A tuple consists of two 4-octet groups and represents data 
       belonging to a sub-carrier. The first tuple represents 
       sub-carrier group 0 and the last tuple represents sub-carrier 
       group (length/8 - 1). In each 4-octet group in the 
       tuple, the most significant byte is loaded first. The order of 
       the tuples is determined by the node to which this type is 
       associated.";
  }

  grouping co-cpe-measurement-parameters {
    description
      "Defines the measurement parameters common between the
       CO SELT PMD and CPE SELT PMD";

    container uncalibrated-echo-response {
      leaf scale-factor {
        type uint32;
        description
          "The scale factor used in the UER measurement";
      }

      leaf uer-g {
        type uint8 {
          range "1 | 2 | 12";
        }
        description
          "The SELT uncalibrated echo response group size (SELT-UER_G)
              is a reported parameter identifying the UER frequency 
              spacing, which is equal to SELT-UER_G x Df with Df = 
              4.3125 kHz. SELT-UER_G has three valid values: 1, 2, and
              12. Section A.2.2.1 refers to SELT-UER_G as the UER 
              granularity parameter, UER_G.";
      }

      leaf uer {
        type per-sub-carrier-int32-tuple;
        description
          "An array of tuples representing the a(i) and b(i) values
           as described below. In each tuple, a(i) is loaded first.";
        reference
          "ITU-T G.996.2 clause A.2.2.1 (SELT-UER-C, SELT-UER-R)";
      }

      description
        "The uncalibrated echo response, UER(i* UER_G*Df), shall be 
         represented in linear format by a scale factor and a 
         normalized complex number a(i)+j*b(i), where i is a frequency
         index i ranging from 0 to NSC-1, the subcarrier spacing, 
         Df = 4.3125 kHz, and (NSC-1) x UER_G x Df is the highest 
         frequency supported by the SELT-PMD functionality. 

         The UER granularity parameter, UER_G, has three valid 
         values: 1, 2, and 12, indicating whether the measurements 
         were performed using a subcarrier spacing of 4.3125 kHz, 
         8.625 kHz, or 51.75 kHz respectively.

         The scale factor shall be coded as a 32-bit unsigned integer.
         Both a(i) and b(i) shall be coded as 32 bit 2's complement 
         signed integers. The value of UER(i* UER_G*Df) shall be 
         defined as: 
           UER(i* UER_G*Df) = (scale/2^31)*(a(i)+j*b(i))/2^31.
         In order to maximize precision, the scale factor shall be 
         chosen such that max(|a(i)|, |b(i)|) over all i is equal to 
         2^31-1. 

         NOTE - This data format supports an UER(f) granularity of 
         2-31 and an UER(f) dynamic range of approximately +6 dB to 
         -186 dB, however it does not imply any future accuracy 
         requirements.

         An UER(i*UER_G* Df) value indicated as a(i) = b(i) = -2^31 is
         a special value. It indicates that no measurement could be 
         done for this subcarrier either because it is not supported 
         by the SELT-PMD function, or that the value is out of range 
         to be represented.";

      reference
        "ITU-T G.996.2 clause A.2.2.1 (SELT-UER-C, SELT-UER-R)";
    }

    leaf uncalibrated-echo-response-variance {
      type per-sub-carrier-uint8;
      description
        "The REL_VAR_UER(f) provides the relative variance of the 
         uncalibrated echo response by the SELT-PMD function for each
         frequency i * UER_G * Df, where i ranges from 0 to NSC-1,
         Df = 4.3125 kHz, and (NSC-1) * UER_G * Df is the highest 
         frequency supported by the SELT-PMD functionality.

         The relative variance of the uncalibrated echo response 
         REL_VAR_UER(i* UER_G *Df) shall be represented as an 8-bit 
         unsigned integer v(i), where i is the subcarrier index 
         i = 0 to NSC-1. The value of REL_VAR_UER(i* UER_G *Df) shall
         be defined as REL_VAR_UER(i* UER_G *Df) = 3 - v(i)/2 dB. 
         The number v(i) is an 8-bit unsigned integer in the range 0 
         to 254. This data format supports a REL_VAR_UER(i) over a 
         range from -124 dB to +3 dB for each carrier with a 
         granularity from 0.5 dB. Out of range values shall be 
         clamped to the closest range bound. The special value v(i) =
         255 indicates that no measurement is available for that
         carrier.";
      reference
        "ITU-T G.996.2 clause A.2.2.2 (SELT-UER-VAR-C, 
         SELT-UER-VAR-R)";
    }

    container quiet-line-noise {

      leaf seltqln-g {
        type uint8 {
          range "1 | 2 | 12";
        }
        description
          "The SELT quiet line noise group size (SELTQLN_G) is a 
           reported parameter identifying the SELTQLN frequency 
           spacing, which is equal to SELTQLN_G x Df with Df = 4.3125 
           kHz. SELTQLN_G has three valid values: 1, 2, and 12.";
      }

      leaf qln {
        type per-sub-carrier-uint8;
        description
          "An array of values representing n(i).";
      }

      description
        "The SELT quiet line noise provides the quiet line noise PSD 
         as measured by the SELT-PMD function (see clause A.1.1.2) for
         each sub-carrier frequency i x SELTQLN_G x Df where i ranges 
         from 0 to NSC-1, Df = 4.3125 kHz, and 
         (NSC-1) x SELTQLN_G x Df is the highest frequency supported 
         by the SELT-PMD functionality. 

         SELTQLN_G has three valid values: 1, 2, and 12, indicating 
         whether the measurements were performed using a subcarrier 
         spacing of 4.3125 kHz,  8.625 kHz, or of 51.75 kHz 
         respectively.

         SELT quiet line noise SELTQLN(i x SELTQLN_G x Df) shall be 
         represented as an 8 bit unsigned integer n(i), where i is the
         subcarrier index i = 0 to NSC-1. The value of 
         SELTQLN(i x SELTQLN_G x Df) shall be defined as 
         SELTQLN(i x SELTQLN_G x Df ) = -23 - (n(i)/2) dBm/Hz. This 
         data format supports a SELTQLN(f) granularity of 0.5 dB and 
         an SELTQLN(f) dynamic range of -150 to -23 dBm/Hz.";
      reference
        "ITU-T G.996.2 clause A.2.2.3 (SELT-QLN-C, SELT-QLN-R)";
    }
  }

  grouping pmd-measurement-parameters {
    description
      "Defines the SELT-PMD measurement parameters.";

    container c {
      description
        "Parameters applicable to the CO SELT PMD";

      uses co-cpe-measurement-parameters;
    }

    container r {
      description
        "Parameters applicable to the CPE SELT PMD";

      uses co-cpe-measurement-parameters;
    }
  }
}
