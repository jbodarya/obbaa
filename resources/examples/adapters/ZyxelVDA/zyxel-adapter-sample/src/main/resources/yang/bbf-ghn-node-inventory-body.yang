submodule bbf-ghn-node-inventory-body {
  yang-version 1.1;
  belongs-to bbf-ghn {
    prefix bbf-ghn;
  }

  import ietf-yang-types {
    prefix yang;
  }

  import bbf-yang-types {
    prefix bbf-yang;
  }

  include bbf-ghn-types;

  organization
    "Broadband Forum <https://www.broadband-forum.org>
     Common YANG Work Area";

  contact
    "Comments or questions about this Broadband Forum YANG module
     should be directed to <mailto:help@broadband-forum.org>.

     Editor:      Marcos Martinez, Marvell Semiconductor Inc.

     PS Leader:   Joey Boyd, ADTRAN

     PS Leader:   Ken Kerpez, ASSIA

     WA Director: Joey Boyd, ADTRAN

     WA Director: Sven Ooghe, Nokia";

  description
    "This module contains a collection of node inventory related YANG
     data types and grouping definitions for the management of
     G.hn lines.

     Copyright (c) 2018, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-374; see
     the TR itself for full legal notices.";

  revision 2018-07-13 {
    description
      "Initial revision.
       * Approval Date:    2018-06-04.
       * Publication Date: see revision date above.";
    reference
      "TR-374: Yang Modules for Management of G.hn Systems in FTTdp 
               Architecture <https://www.broadband-forum.org/technical
                                     /download/TR-374.pdf>";
  }

  grouping node-inventory-parameters {
    description
      "Inventory parameters.";

    leaf certified-vendor-id {
      type bbf-yang:string-ascii64;
      description
        "Certification number of the interface.
         It includes the identification of the vendor 
         of the system integrating the G.hn interface.";
      reference
        "www.homegridforum.org";
    }

    leaf certification-version {
      type bbf-yang:string-ascii64;
      description
        "HomeGrid forum G.hn certification version.";
      reference
        "www.homegridforum.org";
    }

    leaf self-test-passed {
      type boolean;
      description
        "Indicates the result of the self test result.";
    }


    leaf system-serial-number {
      type bbf-yang:string-ascii64;
      description
        "Serial number of the system including
         the G.hn interface.";
    }

    leaf node-mac-address {
      type yang:mac-address;
      description
        "The MAC Address of the interface, denoted as 
         node MAC address or Registration Identifier 
         (REGID) in G.9961.";
      reference
        "ITU-T G.9961 clause 8.6.1";
    }

    leaf software-version {
      type bbf-yang:string-ascii64;
      description
        "Software version of the G.hn interface node.";
    }

    leaf hardware-version {
      type bbf-yang:string-ascii64;
      description
        "Hardware version of the G.hn interface node.";
    }

    leaf manufacturer-oui {
      type bbf-ghn:oui;
      description
        "Organizationally Unique Identifier (OUI) of the manufacturer 
         of the G.hn interface node.";
    }

    leaf model-name {
      type bbf-yang:string-ascii64;
      description
        "Model name of the G.hn interface corresponding to this 
         node.";
    }
  }
}
