submodule bbf-selt-pointers {
  yang-version 1.1;
  belongs-to bbf-selt {
    prefix bbf-selt;
  }

  import ietf-interfaces {
    prefix if;
  }

  include bbf-selt-base;

  /* PMD Control Definitions */
  include bbf-selt-pmd-control-body;

  /* Profile Definitions */
  include bbf-selt-pmd-profiles;
  include bbf-selt-processing-profiles;

  organization
    "Broadband Forum <https://www.broadband-forum.org>
     Common YANG Work Area";

  contact
    "Comments or questions about this Broadband Forum YANG module
     should be directed to <mailto:help@broadband-forum.org>.

     Editor:      Ken Kerpez, ASSIA, Inc.

     Editor:      Joey Boyd, ADTRAN

     PS Leader:   Ken Kerpez, ASSIA, Inc.

     PS Leader:   Joey Boyd, ADTRAN

     WA Director: Sven Ooghe, Nokia

     WA Director: Joey Boyd, ADTRAN";

  description
    "This submodule contains a collection of YANG definitions for
     managing profiles for SELT on supported interfaces.

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a1; see
     the TR itself for full legal notices.";

  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  augment '/if:interfaces/if:interface/bbf-selt:selt' {
    description
      "Data nodes to support the assignment of SELT configuration.";

    leaf pmd-profile {
      type pmd-profile-ref;
      status deprecated;
      description
        "References a SELT-PMD profile. This method of configuration
         has been deprecated. The 'profile-config' method should
         instead be used.";
    }

    leaf processing-profile {
      if-feature "selt-p";
      type leafref {
        path '/bbf-selt:selt/bbf-selt:profiles/bbf-selt:processing-'
           + 'profile/bbf-selt:name';
      }
      status deprecated;
      description
        "References a SELT-P profile. This method of configuration
         has been deprecated. The 'profile-config' method should
         instead be used.";
    }

    container pmd-control {
      status deprecated;
      description
        "Data nodes to support the SELT-PMD control object";

      uses selt-pmd-control {
        status deprecated;
      }
    }

    choice profile-config {
      default "no-profiles-attached";
      description
        "Provides methods attachment of profiles.";

      case no-profiles-attached {
        leaf no-profiles-attached {
          type empty;
          description
            "If present, indicates that no profiles are attached
             to this line";
        }
      }

      case direct-attachment-mode {
        container direct-attachment-mode {
          description
            "Configuration associated with assigning SELT profiles.";

          leaf pmd-profile {
            type pmd-profile-ref;
            mandatory true;
            description
              "References a SELT-PMD profile.";
          }

          leaf processing-profile {
            if-feature "selt-p";
            type leafref {
              path '/bbf-selt:selt/bbf-selt:profiles/bbf-selt:'
                 + 'processing-profile/bbf-selt:name';
            }
            mandatory true;
            description
              "References a SELT-P profile.";
          }
        }
      }
    }
  }
}
