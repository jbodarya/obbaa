submodule bbf-mgmd-configuration-interface-to-router {
  yang-version 1.1;
  belongs-to bbf-mgmd {
    prefix bbf-mgmd-c-i2r;
  }

  organization
    "Broadband Forum <https://www.broadband-forum.org>
     Common YANG Work Area";

  contact
    "Comments or questions about this Broadband Forum YANG module
     should be directed to <mailto:help@broadband-forum.org>.

     Editor:      Joey Boyd, ADTRAN

     Editor:      Ludwig Pauwels, Nokia

     PS Leader:   Joey Boyd, ADTRAN

     PS Leader:   Ken Kerpez, ASSIA

     WA Director: Joey Boyd, ADTRAN

     WA Director: Sven Ooghe, Nokia";

  description
    "This module contains a collection of YANG definitions for 
     supporting the Multicast Group Membership Discovery (MGMD) 
     Protocols. In particular, it describes configuration objects used
     for managing the Internet Group Management Protocol (IGMP) and 
     the Multicast Listener Discovery (MLD) protocol on interfaces 
     that connect to multicast routers.

     Copyright (c) 2017-2018, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383; see
     the TR itself for full legal notices.";

  revision 2018-07-13 {
    description
      "Initial revision.
       * Approval Date:    2018-06-04.
       * Publication Date: see revision date above.";
    reference
      "TR-383: Common YANG Modules
               <https://www.broadband-forum.org/technical/download/
                        TR-383_Amendment-1.pdf>";
  }

  grouping interface-to-router {
    description
      "Grouping of objects used for configuring the Internet Group 
       Management Protocol (IGMP) and the Multicast Listener Discovery
       (MLD) protocol on interfaces that connect multicast routers.";

    leaf unsolicited-report-interval {
      type uint32 {
        range "1..255";
      }
      units "0.1 seconds";
      default "10";
      description
        "The interval between repetitions of a host's initial report
         of interest in a multicast address.";
      reference
        "RFC 3376 Section 8.11;
         RFC 3810 Section 9.11";
    }

    leaf robustness {
      type uint32 {
        range "1..255";
      }
      default "2";
      description
        "The robustness variable allows tuning for the expected packet
         loss on a subnet. If a subnet is expected to be lossy, the
         robustness variable may be increased. IGMP and MLD are robust
         to (robustness variable - 1) packet losses.";
      reference
        "RFC 3376 Section 8.1; 
         RFC 5519 mgmdHostInterfaceVersion3Robustness";
    }
  }
}
