submodule bbf-fast-test-diagnostics {
  yang-version 1.1;
  belongs-to bbf-fast {
    prefix bbf-fast;
  }

  import ietf-interfaces {
    prefix if;
  }

  import bbf-fastdsl {
    prefix bbf-fastdsl;
  }

  include bbf-fast-base;

  /* Test bodies */
  include bbf-fast-test-mode-body;
  include bbf-fast-update-test-body;
  include bbf-fast-link-state-body;
  include bbf-fast-read-test-body;


  organization
    "Broadband Forum <https://www.broadband-forum.org>
     Common YANG Work Area";

  contact
    "Comments or questions about this Broadband Forum YANG module
     should be directed to <mailto:help@broadband-forum.org>.

     Editor:      Ken Kerpez, ASSIA, Inc.

     Editor:      Joey Boyd, ADTRAN

     PS Leader:   Ken Kerpez, ASSIA, Inc.

     PS Leader:   Joey Boyd, ADTRAN

     WA Director: Sven Ooghe, Nokia

     WA Director: Joey Boyd, ADTRAN";

  description
    "This submodule contains a collection of YANG data types and
     grouping definitions for the management of FAST test modes.

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a1; see
     the TR itself for full legal notices.";

  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }



  augment '/if:interfaces/if:interface/bbf-fastdsl:line/bbf-fast:'
        + 'line' {
    description
      "Data nodes to support tests on the line";

    container test-mode {
      description
        "Test modes associated with a line";

      uses line-test-modes;
    }

    container update-test {
      description
        "Update test parameters for a line";

      uses line-update-test-parameters;
    }

    container read-test {
      description
        "Test parameter configuration for a line associated with
         how test parameters are read.";

      uses line-read-test-parameters;
    }

    container link-state {
      description
        "Link state test configuration";

      uses link-state-test-parameters;
    }
  }
}
