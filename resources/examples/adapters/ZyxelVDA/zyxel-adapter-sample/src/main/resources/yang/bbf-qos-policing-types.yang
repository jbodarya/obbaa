module bbf-qos-policing-types {
  yang-version 1.1;
  namespace "urn:bbf:yang:bbf-qos-policing-types";

  prefix bbf-qos-plc-tp;

  organization
    "Broadband Forum <https://www.broadband-forum.org>
     Common YANG Work Area";

  contact
    "Comments or questions about this Broadband Forum YANG module
     should be directed to <mailto:help@broadband-forum.org>.

     Editor:      Joey Boyd, ADTRAN

     Editor:      Ludwig Pauwels, Nokia

     PS Leader:   Joey Boyd, ADTRAN

     PS Leader:   Ken Kerpez, ASSIA

     WA Director: Joey Boyd, ADTRAN

     WA Director: Sven Ooghe, Nokia";

  description
    "This module contains a collection of YANG definitions for 
     supporting the Broadband Forum requirements on the management of
     Quality of Service (QoS) as applicable to access network 
     equipment. As such, this module is specific to access network 
     equipment (e.g., BBF-specified Access Nodes and FTTdp DPUs).

     Specifically, this module contains common types used for 
     management of Policers.

     Copyright (c) 2017-2018, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383; see
     the TR itself for full legal notices.";

  revision 2018-07-13 {
    description
      "Initial revision.
       * Approval Date:    2018-06-04.
       * Publication Date: see revision date above.";
    reference
      "TR-383: Common YANG Modules
               <https://www.broadband-forum.org/technical/download/
                        TR-383_Amendment-1.pdf>";
  }

  typedef information-rate {
    type uint64;
    units "bits per second";
    description
      "Information rate in bits per second.";
  }

  typedef burst-size {
    type uint32;
    units "bytes";
    description
      "Burst size in bytes.";
  }

  typedef coupling-flag {
    type uint8 {
      range "0..1";
    }
    description
      "The Coupling Flag (CF) allows the choice between two modes of
       operation of the rate enforcement algorithm.

       When CF is set to 0, the long term average rate of Service
       Frames that are declared Yellow is bound by EIR.

       When CF is set to 1, the long term average rate of Service
       Frames that are declared Yellow is bound by CIR+EIR depending 
       on the volume of offered Service Frames which are declared 
       Green.

       In both cases, the burst size of Service Frames which are
       declared Yellow is bound by EBS.";
    reference
      "MEF 10.3";
  }

  typedef color-mode {
    type enumeration {
      enum "color-aware" {
        description
          "A Policer property where a pre-determined level of 
           compliance for each Service Frame is taken into account 
           when determining the level of compliance for each Service 
           Frame.";
      }
      enum "color-blind" {
        description
          "A Policer property where a pre-determined level of 
           compliance for each Service Frame, if present, is ignored 
           when determining the level of compliance for each Service 
           Frame.";
      }
    }
    description
      "The Color Mode (CM) indicates the type of color awareness which
       is employed by the Policer.";
    reference
      "MEF 10.3, Section 12.1";
  }
}
