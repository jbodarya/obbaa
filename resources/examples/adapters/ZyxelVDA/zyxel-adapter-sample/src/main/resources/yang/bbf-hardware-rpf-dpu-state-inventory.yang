submodule bbf-hardware-rpf-dpu-state-inventory {
  yang-version 1.1;
  belongs-to bbf-hardware-rpf-dpu-state {
    prefix bbf-hw-rpf-dpu-state;
  }

  organization
    "Broadband Forum <https://www.broadband-forum.org>
     Common YANG Work Area";

  contact
    "Comments or questions about this Broadband Forum YANG module
     should be directed to <mailto:help@broadband-forum.org>.

     Editor:      Ken Kerpez, ASSIA, Inc.

     Editor:      Joey Boyd, ADTRAN

     PS Leader:   Ken Kerpez, ASSIA, Inc.

     PS Leader:   Joey Boyd, ADTRAN

     WA Director: Sven Ooghe, Nokia

     WA Director: Joey Boyd, ADTRAN";

  description
    "This submodule contains a collection of YANG definitions for 
     reporting the inventory data for Reverse Power Feeding (RPF)
     for a Distribution Point Unit (DPU).

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a1; see
     the TR itself for full legal notices.";

  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }

  grouping rpf-near-end-line-inventory {
    description
      "RPF near-end line level inventory.";

    leaf reconfiguration-capability {
      type enumeration {
        enum "none" {
          description
            "No reconfiguration capability.";
        }
        enum "broadband-bypass" {
          description
            "Broadband Bypass.";
        }
        enum "pots-rcr" {
          description
            "POTS Remote Copper Reconfiguration (RCR) 
             Protocol.";
        }
      }
      status deprecated;
      description
        "Reports the ReConfiguration capability for the line.";
      reference
        "ITU-T G.997.2 clause A.7.6.1.1 (DPU-RC)";
    }
  }

  grouping rpf-far-end-line-inventory {
    description
      "RPF far-end line level inventory.";

    leaf nt-integrated {
      type enumeration {
        enum "unknown" {
          description
            "NT integration of the PSE is unknown.";
        }
        enum "not-integrated" {
          description
            "PSE is not integrated into the NT.";
        }
        enum "integrated" {
          description
            "PSE is integrated into the NT.";
        }
      }
      status deprecated;
      description
        "Reports whether the PSE is integrated in the NT, 
         based on the RPF OAM parameter NTE-CPF (see clause 
         A.6.2.7). Until the DPU ME receives an NTE-CPF 
         Indication for the first time, it is unknown whether 
         or not the PSE is integrated in the NT.";
      reference
        "ITU-T G.997.2 clause A.7.6.2.1 (NTE-CPF)";
    }

    leaf battery-backup-available {
      type enumeration {
        enum "unknown" {
          description
            "Battery backup availability is unknown.";
        }
        enum "not-available" {
          description
            "Battery backup is not available.";
        }
        enum "available" {
          description
            "Battery backup is available.";
        }
      }
      status deprecated;
      description
        "Reports whether battery backup is available at the 
         PSE, based on the PSE trying to start up the PE while
         powered on battery (PRP PS field, see section 6.2.5.1
         of [ETSI TS 101 548]) and on the PSE-BAT, PSE-ACM, 
         and PSE-BBA indications (see section 6.3 of 
         [ETSI TS 101 548] and clause A.6.2.2). Until the PE 
         receives the PRP PS field for the first time and 
         until the PE or DPU ME receive a BAT, ACM, or BBA 
         Indication for the first time (whichever occurs 
         first), it is unknown whether or not battery backup 
         is available in the PSE.";
      reference
        "ITU-T G.997.2 clause A.7.6.2.2 (PSE-BBA)";
    }

    leaf prp-capability {
      type enumeration {
        enum "unknown" {
          description
            "PRP capability is unknown.";
        }
        enum "not-supported" {
          description
            "PRP not supported.";
        }
        enum "supported" {
          description
            "PRP supported.";
        }
      }
      status deprecated;
      description
        "Reports the PSE PRP capability. In case the PSE is 
         integrated in the NT (i.e., NT-CPF equals 2), the 
         PSE-PRP capability is communicated through RPF OAM from
         PSE to DPU (see clause A.6.2.7). In case the PSE is not
         integrated in the NT (i.e., NT-CPF equals 2), it is 
         deduced by the DPU from successful PRP start-up, 
         whereby the DPU shall assume that the PRP disconnect 
         trigger is sent by the PSE that is currently providing 
         reverse power to the DPU. Until the PE receives the PRP
         PS field (see clause A.6.2.7) for the first time, or 
         until first successful PRP start-up, the PSE PRP 
         capability is unknown.";
      reference
        "ITU-T G.997.2 clause A.7.6.2.3 (PSE-PRP)";
    }
  }
}
