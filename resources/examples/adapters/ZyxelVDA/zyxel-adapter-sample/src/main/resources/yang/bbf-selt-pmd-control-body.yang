submodule bbf-selt-pmd-control-body {
  yang-version 1.1;
  belongs-to bbf-selt {
    prefix bbf-selt;
  }

  organization
    "Broadband Forum <https://www.broadband-forum.org>
     Common YANG Work Area";

  contact
    "Comments or questions about this Broadband Forum YANG module
     should be directed to <mailto:help@broadband-forum.org>.

     Editor:      Ken Kerpez, ASSIA, Inc.

     Editor:      Joey Boyd, ADTRAN

     PS Leader:   Ken Kerpez, ASSIA, Inc.

     PS Leader:   Joey Boyd, ADTRAN

     WA Director: Sven Ooghe, Nokia

     WA Director: Joey Boyd, ADTRAN";

  description
    "This submodule contains a collection of YANG definitions for
     managing the PMD control object.

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a1; see
     the TR itself for full legal notices.";

  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  typedef pmd-function {
    type enumeration {
      enum "uer-measurement" {
        value 1;
        description
          "Triggers the CO SELT PMD to start a Uncalibrated
           Echo Response (UER) measurement.";
        reference
          "ITU-T G.996.2 clause A.2.3.1 (SELT-UME-C)";
      }
      enum "qln-measurement" {
        value 2;
        description
          "Triggers the CO SELT PMD to start a Quiet Line
           Noise (QLN) measurement.";
        reference
          "ITU-T G.996.2 clause A.2.3.3 (SELT-QME-C)";
      }
    }
    description
      "The SELT PMD function.";
  }

  grouping selt-pmd-control {
    description
      "Defines the parameters contained in the PMD control object.";

    leaf uer-measurement-enable-c {
      type boolean;
      default "false";
      status deprecated;
      description
        "If true, triggers the CO SELT PMD to start a Uncalibrated
         Echo Response(UER) measurement.

         A configuration change back to 'false' is required before 
         initiating another update.";
      reference
        "ITU-T G.996.2 clause A.2.3.1 (SELT-UME-C)";
    }

    leaf qln-measurement-enable-c {
      type boolean;
      default "false";
      status deprecated;
      description
        "If true, triggers the CO SELT PMD to start a Quiet Line
         Noise(QLN) measurement.

         A configuration change back to 'false' is required before 
         initiating another update.";
      reference
        "ITU-T G.996.2 clause A.2.3.3 (SELT-QME-C)";
    }
  }


  grouping pmd-control {
    description
      "PMD control configuration.";

    leaf pmd-control {
      type enumeration {
        enum "disable" {
          description
            "The CO SELT PMD is not configured for a measurement.";
        }
        enum "enable" {
          description
            "The CO SELT PMD is configured for a measurement.";
        }
      }
      default "disable";
      description
        "The CO SELT PMD is by default 'disable'. When 'disable', the 
         line is in normal operation (e.g., in the L0 state if the 
         line is configured with AdminStatus=up). When 'enable', the 
         AN/DPU ME shall force the line to the L3 state.";
    }


    action request-pmd-function-c {
      description
        "A measurement is by default not triggered. A measurement is 
         triggered when the action is sent with the appropriate 
         function specified. One or more measurements may be triggered
         while the CO SELT PMD is configured 'enable', possibly with 
         different CO SELT PMD configuration parameters. If the 
         triggered measurement cannot be executed, then the 
         AN/DPU ME rejects this action and the CO SELT PMD status 
         remains 'inactive'.";

      input {
        leaf pmd-function {
          type union {
            type enumeration {
              enum "abort" {
                value 0;
                description
                  "Triggers the CO SELT PMD to abort any currently
                   ongoing measurement.";
              }
            }
            type pmd-function;
          }
          description
            "The action being requested.";
        }
      }
    }
  }
}
