submodule bbf-software-image-management-common-body {
  yang-version 1.1;
  belongs-to bbf-software-image-management {
    prefix bbf-sim;
  }
  
  import bbf-yang-types {
    prefix bbf-yang;
  }
  
  organization
    "Broadband Forum Common YANG Work Area";

  contact
    "Comments or questions about this Broadband Forum YANG module
     should be directed to <mailto:help@broadband-forum.org>.

     Editor:      TBD
     
     WA Director: William Lupton, Broadband Forum
                  <mailto:wlupton@broadband-forum.org>

     WA Director: Michael Shaffer
                  <mailto:michael.shaffer@nokia.com>";

  description
    "This submodule contains a collection of common YANG definitions 
     used by the other body submodules.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms.

     Any moral rights which are necessary to exercise under the above
     license grant are also deemed granted under this license.

     This version of this YANG module is part of TR-355; see
     the TR itself for full legal notices.";

  revision 2017-03-08 {
    description
      "Initial revision.";
    reference
      "TBD";
  }
  
  feature software-actions {
    description
      "Used to indicate support for invoking actions on software
       images.";
  }
  
  typedef software-name {
    type bbf-yang:string-ascii64;
    description
      "The name of a particular software. Typically, this is the
       filename associated with the software, e.g. 
       software-x.y.z.bin.";
  }
  
  identity failure-reason {
    description
      "The reason a failure occurred.";
  }
  
  identity no-failure {
    description
      "No failure has occurred.";
  }
  
  identity general-error {
    base failure-reason;
    description
      "A general error occurred.";
  }
  
  grouping failure {
    description
      "Objects associated with a failure.";
    
    leaf failure-reason {
      type identityref {
        base failure-reason;
      }
      description
        "The reason the failure occurred.";
    }
    
    leaf failure-string {
      when "../failure-reason != 'no-failure'" {
        description
          "Only valid when there is a failure.";
      }
      type string;
      description
        "A text string indicating the reason for the failure when
         either no defined reason exists or additional information
         is available beyond the definition of the reason.";
    }
  }
  
}
