submodule bbf-fast-line-performance-body {
  yang-version 1.1;
  belongs-to bbf-fast {
    prefix bbf-fast;
  }

  import bbf-yang-types {
    prefix bbf-yang;
  }

  include bbf-fast-perf-types;

  organization
    "Broadband Forum <https://www.broadband-forum.org>
     Common YANG Work Area";

  contact
    "Comments or questions about this Broadband Forum YANG module
     should be directed to <mailto:help@broadband-forum.org>.

     Editor:      Ken Kerpez, ASSIA, Inc.

     Editor:      Joey Boyd, ADTRAN

     PS Leader:   Ken Kerpez, ASSIA, Inc.

     PS Leader:   Joey Boyd, ADTRAN

     WA Director: Sven Ooghe, Nokia

     WA Director: Joey Boyd, ADTRAN";

  description
    "This submodule contains a collection of performance-related
     YANG data types and grouping definitions for the management
     of FAST lines.

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a1; see
     the TR itself for full legal notices.";

  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping line-performance-ftu-o-parameters {
    description
      "Defines the performance parameters applicable only
       to the FTU-O of FAST lines.";

    leaf successful-tiga {
      type bbf-yang:performance-counter32;
      description
        "Reports a count of the successful TIGA primitives
         (success_TIGA). The successful TIGA primitive
         (success_TIGA) is defined in clause 11.3.1.6/G.9701.";
      reference
        "ITU-T G.997.2 clause 7.7.25 (CURR/PREV_NE/FE_15/24_TIGA).";
    }

    leaf full-initializations {
      type bbf-yang:performance-counter32;
      description
        "Reports a count of the full initialization primitives
         (full_init). The full initialization primitive (full_init)
         is defined in clause 11.3.1.5/G.9701. ";
      reference
        "ITU-T G.997.2 clause 7.7.13 (CURR/PREV_15/24_FULL_INITS).";
    }

    leaf failed-full-initializations {
      type bbf-yang:performance-counter32;
      description
        "Reports a count of the failed full initialization
         primitives(failedfull_init). The failed full initialization
         primitive(failedfull_init) is defined in clause
         11.3.1.5/G.9701.";
      reference
        "ITU-T G.997.2 clause 7.7.14
         (CURR/PREV_15/24_FAILEDFULL_INITS).";
    }

    leaf fast-initializations {
      type bbf-yang:performance-counter32;
      description
        "Reports a count of the fast initialization primitives
         (fast_init). The fast initialization primitive (fast_init)
         is defined in clause 11.3.1.5/G.9701.";
      reference
        "ITU-T G.997.2 clause 7.7.15 (CURR/PREV_15/24_FAST_INITS).";
    }

    leaf failed-fast-initializations {
      type bbf-yang:performance-counter32;
      description
        "Reports a count of the failed fast initialization
         primitives(failedfast_init). The failed fast initialization
         primitive(failedfast_init) is defined in clause
         11.3.1.5/G.9701.";
      reference
        "ITU-T G.997.2 clause 7.7.16
         (CURR/PREV_15/24_FAILEDFAST_INITS).";
    }

    leaf loss-of-power-interruptions {
      type bbf-yang:performance-counter32;
      description
        "Reports a count of the loss-of-power interruption anomalies
         (lpr_intrpt). The loss-of-power interruption anomaly
         (lpr_intrpt) is defined in clause 11.3.1.1/G.9701.";
      reference
        "ITU-T G.997.2 clause 7.7.17 (CURR/PREV_15/24_LPR_INTRPT).";
    }

    leaf host-reinit-interruptions {
      type bbf-yang:performance-counter32;
      description
        "Reports a count of the host-reinit interruption anomalies
         (hri_intrpt). The host-reinit interruption anomaly
         (hri_intrpt) is defined in clause 11.3.1.1/G.9701.";
      reference
        "ITU-T G.997.2 clause 7.7.18 (CURR/PREV_15/24_HRI_INTRPT).";
    }

    leaf spontaneous-interruptions {
      type bbf-yang:performance-counter32;
      description
        "Reports a count of the spontaneous interruption anomalies
         (spont_intrpt). The spontaneous interruption anomaly
         (spont_intrpt) is defined in clause 11.3.1.1/G.9701.";
      reference
        "ITU-T G.997.2 clause 7.7.19 
         (CURR/PREV_15/24_SPONT_INTRPT).";
    }
  }

  grouping line-performance-ftu-o-15min-parameters {
    description
      "Defines the 15 minute performance parameters applicable only
       to the FTU-O of FAST lines.";

    leaf link-state-l2.1n-seconds {
      type seconds-counter-15min;
      units "1 second";
      description
        "Reports the time spent in LinkState L2.1N in seconds, 
         accumulated over the relevant period, rounded up to the 
         nearest second.";
      reference
        "ITU-T G.997.2 clause 7.14.3.1
         (CURR/PREV_15/24_L21N); ITU-T G.9701 Table Z-5";
    }

    leaf link-state-l2.1b-seconds {
      type seconds-counter-15min;
      units "1 second";
      description
        "Reports the time spent in LinkState L2.1B in seconds, 
         accumulated over the relevant period, rounded up to the 
         nearest second.";
      reference
        "ITU-T G.997.2 clause 7.14.3.2
         (CURR/PREV_15/24_L21B); ITU-T G.9701 Table Z-5";
    }

    leaf link-state-l2.2-seconds {
      type seconds-counter-15min;
      units "1 second";
      description
        "Reports the time spent in LinkState L2.2 in seconds, 
         accumulated over the relevant period, rounded up to the 
         nearest second.";
      reference
        "ITU-T G.997.2 clause 7.14.3.3
         (CURR/PREV_15/24_L22); ITU-T G.9701 Table Z-5";
    }
  }

  grouping line-performance-ftu-o-24hr-parameters {
    description
      "Defines the 24 hour performance parameters applicable only
       to the FTU-O of FAST lines.";

    leaf link-state-l2.1n-seconds {
      type seconds-counter-24hr;
      units "1 second";
      description
        "Reports the time spent in LinkState L2.1N in seconds, 
         accumulated over the relevant period, rounded up to the 
         nearest second.";
      reference
        "ITU-T G.997.2 clause 7.14.3.1
         (CURR/PREV_15/24_L21N); ITU-T G.9701 Table Z-5";
    }

    leaf link-state-l2.1b-seconds {
      type seconds-counter-24hr;
      units "1 second";
      description
        "Reports the time spent in LinkState L2.1B in seconds, 
         accumulated over the relevant period, rounded up to the 
         nearest second.";
      reference
        "ITU-T G.997.2 clause 7.14.3.2
         (CURR/PREV_15/24_L21B); ITU-T G.9701 Table Z-5";
    }

    leaf link-state-l2.2-seconds {
      type seconds-counter-24hr;
      units "1 second";
      description
        "Reports the time spent in LinkState L2.2 in seconds, 
         accumulated over the relevant period, rounded up to the 
         nearest second.";
      reference
        "ITU-T G.997.2 clause 7.14.3.3
         (CURR/PREV_15/24_L22); ITU-T G.9701 Table Z-5";
    }
  }

  grouping line-performance-parameters {
    description
      "Defines the performance parameters for FAST lines.";

    leaf loss-of-signal {
      type bbf-yang:performance-counter32;
      description
        "Reports a count of the Loss-of-signal (LOS) failures.";
      reference
        "ITU-T G.997.2 clause 7.7.4 (CURR/PREV_NE/FE_15/24_LOS).";
    }

    leaf loss-of-margin {
      type bbf-yang:performance-counter32;
      description
        "Reports a count of the Loss-of-margin (LOM) failures.";
      reference
        "ITU-T G.997.2 clause 7.7.6 (CURR/PREV_NE/FE_15/24_LOM).";
    }

    leaf loss-of-rmc {
      type bbf-yang:performance-counter32;
      description
        "Reports a count of the Loss-of-RMC (LOR) failures.";
      reference
        "ITU-T G.997.2 clause 7.7.5 (CURR/PREV_NE/FE_15/24_LOR).";
    }

    leaf loss-of-power {
      type bbf-yang:performance-counter32;
      description
        "reports a count of the Loss-of-power (LPR) failures.";
      reference
        "ITU-T G.997.2 clause 7.7.7 (CURR/PREV_NE/FE_15/24_LPR).";
    }

    leaf successful-bit-swaps {
      type bbf-yang:performance-counter32;
      description
        "Reports a count of the successful bit swap primitives
         (success_BSW). The successful bit swap primitive
         (success_BSW) is defined in clause 11.3.1.6/G.9701.";
      reference
        "ITU-T G.997.2 clause 7.7.21 (CURR/PREV_NE/FE_15/24_BSW).";
    }

    leaf successful-autonomous-sra {
      type bbf-yang:performance-counter32;
      description
        "Reports a count of the successful autonomous SRA primitives
         (success_SRA). The successful autonomous SRA primitive
         (success_SRA) is defined in clause 11.3.1.6/G.9701.";
      reference
        "ITU-T G.997.2 clause 7.7.22 (CURR/PREV_NE/FE_15/24_SRA).";
    }

    leaf successful-fra {
      type bbf-yang:performance-counter32;
      description
        "Reports a count of the successful FRA primitives
         (success_FRA). The successful FRA primitive (success_FRA)
         is defined in clause 11.3.1.6/G.9701.";
      reference
        "ITU-T G.997.2 clause 7.7.23 (CURR/PREV_NE/FE_15/24_FRA).";
    }

    leaf successful-rpa {
      type bbf-yang:performance-counter32;
      description
        "Reports a count of the successful RPA primitives
         (success_RPA). The successful RPA primitive (success_RPA)
         is defined in clause 11.3.1.6/G.9701.";
      reference
        "ITU-T G.997.2 clause 7.7.24 (CURR/PREV_NE/FE_15/24_RPA).";
    }
  }

  grouping line-performance-15min-parameters {
    description
      "Defines the 15 minute performance parameters for FAST lines.";

    leaf errored-seconds {
      type seconds-counter-15min;
      description
        "Reports the count of errored seconds (ES). An errored
         second (ES) is defined in clause 11.4.4.2/G.9701.";
      reference
        "ITU-T G.997.2 clause 7.7.8 (CURR/PREV_NE/FE_15/24_ES).";
    }

    leaf severely-errored-seconds {
      type seconds-counter-15min;
      description
        "Reports the count of severely errored seconds (SES).
         A severely errored second (SES) is defined in clause
         11.4.4.3/G.9701.";
      reference
        "ITU-T G.997.2 clause 7.7.9 (CURR/PREV_NE/FE_15/24_SES).";
    }

    leaf loss-of-signal-seconds {
      type seconds-counter-15min;
      description
        "Reports the count of los seconds (LOSS).
         A los second (LOSS) is defined in clause 11.4.4.4/G.9701.";
      reference
        "ITU-T G.997.2 clause 7.7.10 (CURR/PREV_NE/FE_15/24_LOSS).";
    }

    leaf loss-of-rmc-seconds {
      type seconds-counter-15min;
      description
        "Reports the count of lor seconds (LORS). A lor second
         (LORS) is defined in clause 11.4.4.5/G.9701.";
      reference
        "ITU-T G.997.2 clause 7.7.11 (CURR/PREV_NE/FE_15/24_LORS).";
    }

    leaf unavailable-seconds {
      type seconds-counter-15min;
      description
        "Reports the count of unavailable seconds (UAS). An
         unavailable second (UAS) is defined in clause
         11.4.4.6/G.9701.";
      reference
        "ITU-T G.997.2 clause 7.7.12 (CURR/PREV_NE/FE_15/24_UAS).";
    }
  }

  grouping line-performance-24hr-parameters {
    description
      "Defines the 24 hour performance parameters for FAST lines.";

    leaf errored-seconds {
      type seconds-counter-24hr;
      description
        "Reports the count of errored seconds (ES). An errored
         second (ES) is defined in clause 11.4.4.2/G.9701.";
      reference
        "ITU-T G.997.2 clause 7.7.8 (CURR/PREV_NE/FE_15/24_ES).";
    }

    leaf severely-errored-seconds {
      type seconds-counter-24hr;
      description
        "Reports the count of severely errored seconds (SES).
         A severely errored second (SES) is defined in clause
         11.4.4.3/G.9701.";
      reference
        "ITU-T G.997.2 clause 7.7.9 (CURR/PREV_NE/FE_15/24_SES).";
    }

    leaf loss-of-signal-seconds {
      type seconds-counter-24hr;
      description
        "Reports the count of los seconds (LOSS).
         A los second (LOSS) is defined in clause 11.4.4.4/G.9701.";
      reference
        "ITU-T G.997.2 clause 7.7.10 (CURR/PREV_NE/FE_15/24_LOSS).";
    }

    leaf loss-of-rmc-seconds {
      type seconds-counter-24hr;
      description
        "Reports the count of lor seconds (LORS). A lor second
         (LORS) is defined in clause 11.4.4.5/G.9701.";
      reference
        "ITU-T G.997.2 clause 7.7.11 (CURR/PREV_NE/FE_15/24_LORS).";
    }

    leaf unavailable-seconds {
      type seconds-counter-24hr;
      description
        "Reports the count of unavailable seconds (UAS). An
         unavailable second (UAS) is defined in clause
         11.4.4.6/G.9701.";
      reference
        "ITU-T G.997.2 clause 7.7.12 (CURR/PREV_NE/FE_15/24_UAS).";
    }
  }

  grouping line-performance {
    description
      "Defines the parameters required for performance
       management of FAST lines.";

    container performance {
      description
        "Performance parameters";

      container intervals-15min {
        description
          "15 minute interval performance history";

        container current {
          description
            "Contains the counts that are currently accumulating.";

          container ftu-o {
            description
              "Fast Transceiver Unit - central Office";

            uses performance-history-measured-time;
            uses line-performance-parameters;
            uses line-performance-15min-parameters;
            uses line-performance-ftu-o-parameters;
            uses line-performance-ftu-o-15min-parameters;
          }

          container ftu-r {
            description
              "Fast Transceiver Unit - Remote side";

            uses performance-history-measured-time;
            uses line-performance-parameters;
            uses line-performance-15min-parameters;
          }
        }

        uses performance-15min-history-parameters;

        list history {
          key "interval-number";
          max-elements 96;
          ordered-by system;
          description
            "A history of 15 minute intervals.";

          leaf interval-number {
            type performance-15min-history-interval;
            description
              "The number of the interval relative to the current
               interval.";
          }

          container ftu-o {
            description
              "Fast Transceiver Unit - central Office";

            uses performance-history-15min-interval-parameters;
            uses line-performance-parameters;
            uses line-performance-15min-parameters;
            uses line-performance-ftu-o-parameters;
            uses line-performance-ftu-o-15min-parameters;
          }

          container ftu-r {
            description
              "Fast Transceiver Unit - Remote side";

            uses performance-history-15min-interval-parameters;
            uses line-performance-parameters;
            uses line-performance-15min-parameters;
          }
        }
      }


      container intervals-24hr {
        if-feature "performance-24hr";
        description
          "24 hour interval performance history";

        container current {
          description
            "Contains the counts that are currently accumulating.";

          container ftu-o {
            description
              "Fast Transceiver Unit - central Office";

            uses performance-history-measured-time;
            uses line-performance-parameters;
            uses line-performance-24hr-parameters;
            uses line-performance-ftu-o-parameters;
            uses line-performance-ftu-o-24hr-parameters;
          }

          container ftu-r {
            description
              "Fast Transceiver Unit - Remote side";

            uses performance-history-measured-time;
            uses line-performance-parameters;
            uses line-performance-24hr-parameters;
          }
        }

        uses performance-24hr-history-parameters;

        list history {
          key "interval-number";
          max-elements 7;
          ordered-by system;
          description
            "A history of 24 hour intervals.";

          leaf interval-number {
            type performance-24hr-history-interval;
            description
              "The number of the interval relative to the current
               interval.";
          }

          container ftu-o {
            description
              "Fast Transceiver Unit - central Office";

            uses performance-history-24hr-interval-parameters;
            uses line-performance-parameters;
            uses line-performance-24hr-parameters;
            uses line-performance-ftu-o-parameters;
            uses line-performance-ftu-o-24hr-parameters;
          }

          container ftu-r {
            description
              "Fast Transceiver Unit - Remote side";

            uses performance-history-24hr-interval-parameters;
            uses line-performance-parameters;
            uses line-performance-24hr-parameters;
          }
        }
      }
    }
  }
}
