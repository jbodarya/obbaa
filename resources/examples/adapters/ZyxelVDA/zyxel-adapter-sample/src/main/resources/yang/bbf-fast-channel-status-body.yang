submodule bbf-fast-channel-status-body {
  yang-version 1.1;
  belongs-to bbf-fast {
    prefix bbf-fast;
  }

  import bbf-yang-types {
    prefix bbf-yang;
  }

  organization
    "Broadband Forum <https://www.broadband-forum.org>
     Common YANG Work Area";

  contact
    "Comments or questions about this Broadband Forum YANG module
     should be directed to <mailto:help@broadband-forum.org>.

     Editor:      Ken Kerpez, ASSIA, Inc.

     Editor:      Joey Boyd, ADTRAN

     PS Leader:   Ken Kerpez, ASSIA, Inc.

     PS Leader:   Joey Boyd, ADTRAN

     WA Director: Sven Ooghe, Nokia

     WA Director: Joey Boyd, ADTRAN";

  description
    "This submodule contains a collection of status-related
     YANG data types and grouping definitions for the management
     of FAST bearer channels.

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a1; see
     the TR itself for full legal notices.";

  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }

  grouping channel-status-parameters {
    description
      "Bearer channel status parameters applicable to both
       upstream and downstream.";

    leaf net-data-rate {
      type bbf-yang:data-rate32-or-undetermined;
      description
        "Reports the NDR as defined in clause 11.4.1.1.1 of 
         [ITU-T G.9701]. A special value (undetermined) indicates that
         the NDR is undetermined. The object is updated only in L0 
         link state.";
      reference
        "ITU-T G.997.2 clause 7.11.1.1 (NDR).";
    }

    leaf net-data-rate-in-l2.1 {
      type bbf-yang:data-rate32-or-undetermined;
      description
        "Reports the NDR in L2.1N and L2.1B link states as defined in
         clause 11.4.1.1.12 of [ITU-T G.9701]. A special value 
         (undetermined) indicates that the NDR is undetermined. The 
         object is updated only in L2.1N and L2.1B link states.";
      reference
        "ITU-T G.997.2 clause 7.11.6.1 (L2.1-NDRds/us).";
    }

    leaf net-data-rate-in-l2.2 {
      type bbf-yang:data-rate32-or-undetermined;
      description
        "Reports the NDR in L2.2 link state as defined in clause 
         11.4.1.1.13 of [ITU-T G.9701]. A special value (undetermined)
         indicates that the NDR is undetermined. The object is 
         updated only in L2.2 link state. ";
      reference
        "ITU-T G.997.2 clause 7.11.6.2 (L2.2-NDRds/us)";
    }

    leaf expected-throughput {
      type bbf-yang:data-rate32-or-undetermined;
      description
        "Reports the expected throughput as defined in clause 
         11.4.1.1.3 of [ITU-T G.9701]. A special value (undetermined) 
         indicates that the NDR is undetermined. The object is updated
         only in L0 link state.";
      reference
        "ITU-T G.997.2 clause 7.11.1.2 (ETR).";
    }

    leaf expected-throughput-in-l2.1 {
      type bbf-yang:data-rate32-or-undetermined;
      description
        "Reports the expected throughput in L2.1N and L2.1B link 
         state as defined in clause 11.4.1.1.14 of [ITU-T G.9701]. A 
         special value (undetermined) indicates that the expected 
         throughput is undetermined. The object is updated only in 
         L2.1N and L2.1B link states.";
      reference
        "ITU-T G.997.2 clause 7.11.6.3 (L2.1-ETRds/us).";
    }

    leaf expected-throughput-in-l2.2 {
      type bbf-yang:data-rate32-or-undetermined;
      description
        "Reports the expected throughput in L2.2 link state as 
         defined in clause 11.4.1.1.15 of [ITU-T G.9701]. A special 
         value (undetermined) indicates that the expected throughput 
         is undetermined. The object is updated only in L2.2 link 
         state.";
      reference
        "ITU-T G.997.2 clause 7.11.6.4 (L2.2-ETRds/us).";
    }

    leaf gamma-data-rate {
      type bbf-yang:data-rate32-or-undetermined;
      description
        "Reports the NDR as defined in clause 7.11.1.1, lowered by any
         throughput capability limitations remaining in the DRA or L2+
         functions, assuming no user data is transmitted over all the 
         other lines. A special value (undetermined) indicates that 
         the NDR is undetermined. The object is updated only in L0 
         link state.";
      reference
        "ITU-T G.997.2 clause 7.11.1.3 (GDR).";
    }

    leaf attainable-net-data-rate {
      type bbf-yang:data-rate32-or-undetermined;
      description
        "Reports the attainable NDR as defined in clause 11.4.1.1.2 of
         [ITU-T G.9701]. A special value (undetermined) indicates that
         the attainable NDR is undetermined. The object is updated 
         only in L0 link state.";
      reference
        "ITU-T G.997.2 clause 7.11.2.1 (ATTNDR).";
    }

    leaf attainable-expected-throughput {
      type bbf-yang:data-rate32-or-undetermined;
      description
        "Reports the attainable expected throughput as defined in 
         clause 11.4.1.1.4 of [ITU-T G.9701]. A special value 
         (undetermined) indicates that the attainable expected 
         throughput is undetermined. The object is updated only in L0 
         link state.";
      reference
        "ITU-T G.997.2 clause 7.11.2.2 (ATTETR).";
    }

    leaf attainable-gamma-data-rate {
      type bbf-yang:data-rate32-or-undetermined;
      description
        "Reports the attainable NDR (as defined in clause 7.11.2.1), 
         lowered by any throughput capability limitations remaining in
         the DRA or L2+ functions, assuming no user data is 
         transmitted over all the other Lines, and assuming MAXGDR (as
         defined in clause 7.2.1.3) is configured to its maximum valid
         value. A special value (undetermined) indicates that the 
         attainable GDR is undetermined. The object is updated only in
         L0 link state.";
      reference
        "ITU-T G.997.2 clause 7.11.2.3 (ATTGDR).";
    }


    /* G.997.2 Clause 7.11.3 Actual impules noise protection */
    leaf actual-inp-against-shine {
      type uint16 {
        range "0..2046 | 2047";
      }
      units "1 symbol";
      description
        "Reports the actual INP against SHINE as defined in
         clause 11.4.1.1.4/G.9701. A special value, 2047,
         indicates an actual INP against SHINE of 2047 symbols
         or higher.";
      reference
        "ITU-T G.997.2 clause 7.11.3.1 (ACTINP); ITU-T G.9701
         Clause 11.4.1.1.4.";
    }

    leaf actual-inp-against-rein {
      type uint8 {
        range "0..62 | 63";
      }
      units "1 symbol";
      description
        "Reports the actual INP against REIN as defined in
         clause 11.4.1.1.5/G.9701. A special value indicates
         an actual INP against REIN of 63 symbols or higher.";
      reference
        "ITU-T G.997.2 clause 7.11.3.2 (ACTINP_REIN); ITU-T
         G.9701 Clause 11.4.1.1.5.";
    }

    /* G.997.2 Clause 7.11.4 Actual framer settings */
    leaf dtu-fec-codeword-length {
      type uint8 {
        range "32..255";
      }
      units "bytes";
      description
        "Reports the DTU FEC codeword length as defined in
         clause 9.3/G.9701.";
      reference
        "ITU-T G.997.2 clause 7.11.4.1 (DTU-NFEC); ITU-T
         G.9701 Clause 9.3.";
    }

    leaf dtu-fec-redundancy {
      type uint8 {
        range "2 | 4 | 6 | 8 | 10 | 12 | 16";
      }
      units "bytes";
      description
        "Reports the DTU FEC codeword redundancy as defined
         in clause 9.3/G.9701.";
      reference
        "ITU-T G.997.2 clause 7.11.4.2 (DTU-RFEC); ITU-T
         G.9701 Clause 9.3.";
    }

    leaf fec-codewords-per-dtu {
      type uint8 {
        range "1..16";
      }
      description
        "Reports the number of FEC codeword per DTU as defined
         in clause 9.3/G.9701.";
      reference
        "ITU-T G.997.2 clause 7.11.4.3 (DTU_Q); ITU-T G.9701
         Clause 9.3.";
    }
  }

  grouping channel-status {
    description
      "Defines the parameters that define the operational status
       of a FAST bearer channel.";

    container downstream {
      description
        "Downstream channel status";

      uses channel-status-parameters;
    }

    container upstream {
      description
        "Upstream channel status";

      uses channel-status-parameters;
    }
  }
}
