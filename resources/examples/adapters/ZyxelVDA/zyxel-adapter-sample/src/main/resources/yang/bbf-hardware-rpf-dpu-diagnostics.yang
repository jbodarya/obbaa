submodule bbf-hardware-rpf-dpu-diagnostics {
  yang-version 1.1;
  belongs-to bbf-hardware-rpf-dpu {
    prefix bbf-hw-rpf-dpu;
  }

  organization
    "Broadband Forum <https://www.broadband-forum.org>
     Common YANG Work Area";

  contact
    "Comments or questions about this Broadband Forum YANG module
     should be directed to <mailto:help@broadband-forum.org>.

     Editor:      Ken Kerpez, ASSIA, Inc.

     Editor:      Joey Boyd, ADTRAN

     PS Leader:   Ken Kerpez, ASSIA, Inc.

     PS Leader:   Joey Boyd, ADTRAN

     WA Director: Sven Ooghe, Nokia

     WA Director: Joey Boyd, ADTRAN";

  description
    "This submodule contains a collection of YANG definitions for 
     reporting the diagnostic data for Reverse Power Feeding (RPF)
     for a Distribution Point Unit (DPU).

     Copyright (c) 2016-2018 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355a1; see
     the TR itself for full legal notices.";

  revision 2018-10-01 {
    description
      "Amendment 1.
       * Approval Date:    2018-10-01
       * Publication Date: 2018-10-01.";
    reference
      "TR-355a1: YANG Modules for FTTdp Management
                 <https://www.broadband-forum.org/technical/download/
                        TR-355_Amendment-1.pdf>";
  }

  grouping rpf-far-end-line-diagnostics {
    description
      "RPF line level diagnostics.";

    leaf latest-pse-start-up-failure-cause {
      type enumeration {
        enum "no-failure" {
          description
            "No failure detected.";
        }
        enum "elc-0" {
          description
            "Open tip-to-ring.";
        }
        enum "elc-1" {
          description
            "Short tip-to-ring.";
        }
        enum "elc-2" {
          description
            "POTS Exchange (foreign) DC voltage.";
        }
        enum "elc-3" {
          description
            "Off-hook phone.";
        }
        enum "rpf-class-mismatch" {
          description
            "Mismatch of the PSE RPF Class with the DPU RPF
             Class.";
        }
        enum "unknown" {
          description
            "Unknown failure.";
        }
        enum "other" {
          description
            "Failure other than off-hook.";
        }
      }
      description
        "Reports the latest PSE Start-Up Failure indication, 
         detected during 'Start-Up'.";
      reference
        "ITU-T G.997.2 clause A.7.5.2.1 (PSE-SUF)";
    }

    leaf latest-pse-shutdown-cause {
      type enumeration {
        enum "no-shutdown" {
          description
            "No PSE shutdown yet.";
        }
        enum "elc-0" {
          description
            "Open tip-to-ring.";
        }
        enum "elc-1" {
          description
            "Short tip-to-ring.";
        }
        enum "elc-3" {
          description
            "Off-hook phone.";
        }
        enum "overload-time-violation" {
          description
            "Overload time violation as defined in Table 35 of 
             [ETSI TS 101 548].";
        }
        enum "maintain-power-signature-violation" {
          description
            "Maintain power signature violation as defined in 
             Table 37 of [ETSI TS 101 548].";
        }
        enum "unknown" {
          description
            "Unknown shutdown cause.";
        }
      }
      description
        "Reports the latest PSE ShutDown cause, detected during 
         'Normal Operation'.";
      reference
        "ITU-T G.997.2 clause A.7.5.2.2 (PSE-SDC)";
    }
  }
}
